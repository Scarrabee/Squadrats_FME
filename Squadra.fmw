FME workspace Squadra.fmw
Title: Squadrats_FME
Description: FME workspace for processing Squadrats KML files: Generation Yards and übersquares
History: 01/01/2026,Scarrabee,Version 0.5,03/01/2026,Scarrabee,0.6 - 2 by 2 uber incl + extra uber blocks

Parameters:
- SourceDataset_OGCKML = $(FME_MF_DIR)Bron\squadrats-2026-01-02_CORNEEL.kml   # Source Squadrats KML
- ConnectedAreas = 3   # Say how many connected areas you want the workspace to analyse. I advise 3 the limit calculation power
- Tiles_Templocation = $(FME_MF_DIR)Tiles   # Select output for the temp location of the tiles
- OutputLocation = $(FME_MF_DIR_USERTYPED)Export   # Destination KML File
- YardOutput = $(OutputLocation)/Yards.kml

Readers:
- OGCKML_1: OGCKML from $(SourceDataset_OGCKML)

Writers:
- OGCKML_2: OGCKML to $(YardOutput)

Note: Change to you most recent KML
Placemark (reader OGCKML_1)
    -> Sampler
Yardhino (writer OGCKML_2)
    attributes: Yardhino kml_real64
Junction_13
    -> Junction_12
Junction
    -> Junction_2
Junction_2
    -> Junction_3
    -> NeighborFinder_4 [CANDIDATE]
    -> FeatureJoiner_4 [LEFT]
    -> NeighborFinder_5 [CANDIDATE]
    -> FeatureJoiner_5 [LEFT]
    -> NeighborFinder_8 [CANDIDATE]
    -> FeatureJoiner_8 [LEFT]
Junction_12
    -> Junction_11
Junction_3
    -> NeighborFinder_9 [CANDIDATE]
    -> FeatureJoiner_9 [LEFT]
    -> NeighborFinder_10 [CANDIDATE]
    -> FeatureJoiner_10 [LEFT]
    -> NeighborFinder_11 [CANDIDATE]
    -> FeatureJoiner_11 [LEFT]
    -> Junction_6
Junction_11
    -> Junction_10
Junction_6
    -> NeighborFinder_13 [CANDIDATE]
    -> FeatureJoiner_13 [LEFT]
    -> NeighborFinder_14 [CANDIDATE]
    -> FeatureJoiner_14 [LEFT]
    -> NeighborFinder_15 [CANDIDATE]
    -> FeatureJoiner_15 [LEFT]
    -> Junction_7
Junction_10
    -> Junction_9
Junction_7
    -> NeighborFinder_16 [CANDIDATE]
    -> FeatureJoiner_16 [LEFT]
    -> NeighborFinder_17 [CANDIDATE]
    -> FeatureJoiner_17 [LEFT]
    -> NeighborFinder_18 [CANDIDATE]
    -> FeatureJoiner_18 [LEFT]
    -> Junction_8
Junction_9
    -> Junction_4
Junction_8
    -> NeighborFinder_19 [CANDIDATE]
    -> FeatureJoiner_19 [LEFT]
    -> NeighborFinder_20 [CANDIDATE]
    -> FeatureJoiner_20 [LEFT]
    -> NeighborFinder_21 [CANDIDATE]
    -> FeatureJoiner_21 [LEFT]
Junction_4
    -> Tester_7
Junction_18
    -> Junction_5
Junction_5
    -> Junction_16
    -> NeighborFinder_22 [CANDIDATE]
    -> FeatureJoiner_22 [LEFT]
    -> NeighborFinder_23 [CANDIDATE]
    -> FeatureJoiner_23 [LEFT]
    -> NeighborFinder_24 [CANDIDATE]
    -> FeatureJoiner_24 [LEFT]
    -> NeighborFinder_25 [CANDIDATE]
    -> FeatureJoiner_25 [LEFT]
Junction_16
    -> FeatureJoiner_29 [LEFT]
    -> NeighborFinder_29 [CANDIDATE]
    -> FeatureJoiner_28 [LEFT]
    -> NeighborFinder_28 [CANDIDATE]
    -> FeatureJoiner_27 [LEFT]
    -> NeighborFinder_27 [CANDIDATE]
    -> FeatureJoiner_26 [LEFT]
    -> NeighborFinder_26 [CANDIDATE]
    -> Junction_15
Junction_15
    -> FeatureJoiner_33 [LEFT]
    -> NeighborFinder_33 [CANDIDATE]
    -> FeatureJoiner_32 [LEFT]
    -> NeighborFinder_32 [CANDIDATE]
    -> FeatureJoiner_31 [LEFT]
    -> NeighborFinder_31 [CANDIDATE]
    -> FeatureJoiner_30 [LEFT]
    -> NeighborFinder_30 [CANDIDATE]
    -> Junction_20
Junction_20
    -> FeatureJoiner_37 [LEFT]
    -> NeighborFinder_37 [CANDIDATE]
    -> FeatureJoiner_36 [LEFT]
    -> NeighborFinder_36 [CANDIDATE]
    -> FeatureJoiner_35 [LEFT]
    -> NeighborFinder_35 [CANDIDATE]
    -> FeatureJoiner_34 [LEFT]
    -> NeighborFinder_34 [CANDIDATE]
Junction_14
    -> Junction_17
Junction_17
    -> Junction_19
Junction_19
    -> Junction_21
Junction_21
    -> Tester_7
Note: This to export but with filtering, only hold the biggest squares and not the squares withing squares
Tester_7
    BOOL_OP = OR
    TEST_CLAUSE = TEST @Value(Uber) > 19
    TEST_MODE = TEST

Bookmark: Making tiles
Sampler
    RATE = 1
    SAMPLE_MODE = No
    SAMPLE_TYPE_LONG = First N Features
    SAMPLED -> AttributeManager_5
    NOT_SAMPLED -> Sampler_2
Note: For now only worked with Squardhinos, Proces works the same with squares (zoom 14)
AttributeManager_5 [off]
    ATTR_TABLE = SET_TO Name (buffer) = Squares
Sampler_2
    RATE = 1
    SAMPLE_MODE = No
    SAMPLE_TYPE_LONG = First N Features
    SAMPLED -> Deaggregator
    NOT_SAMPLED -> Sampler_3
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AttributeManager_3
AttributeManager_3
    ATTR_TABLE:
      SET_TO Name (buffer) = Squadrino
      RENAME_SET_VALUE _part_number > Oppervlakte (uint64) = @Area()
      REMOVE _geometry_name (buffer)
    -> Sorter
Sorter
    SORT_PARM = Oppervlakte NUMERIC DESCENDING
    SORTED -> Sampler_5
Note: Only the biggers X connected area's to limit calculation power
Sampler_5
    RATE = $(ConnectedAreas)
    SAMPLE_MODE = No
    SAMPLE_TYPE_LONG = First N Features
    SAMPLED -> FeatureWriter [Output]
    SAMPLED -> Sampler_7
Note: Tiling the KML - this step takes the time
FeatureWriter [off]
    DATASET = $(Tiles_Templocation)/Squadrinos.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 17
    MBTILES_MVT_MAX_FEATURES = 200000
    MBTILES_MVT_MAX_SIZE = 500000
    MBTILES_MVT_MINZOOM = 17
    MBTILES_MVT_OVERWRITE_DB = Yes
    MBTILES_MVT_SIMPLIFICATION = 0.0
    MBTILES_MVT_SIMPLIFICATION_MAX_ZOOM = 0.0
    MBTILES_MVT_WRITE_NULLS = YES
    TOTAL_FEATURES_WRITTEN_ATTR = _total_features_written
    SUMMARY -> FeatureReader [INITIATOR]
Note: For testing
Sampler_7
    RATE = 1
    SAMPLE_MODE = No
    SAMPLE_TYPE_LONG = Last N Features
    SAMPLED -> FeatureReader [INITIATOR]
FeatureReader
    ATTRIBUTES = Output,"Name,Oppervlakte"
    ATTR_ACCUM_MODE = Only Use Result
    COMBINE_GEOM = Use Result
    DATASET = $(Tiles_Templocation)/Squadrinos.mbtiles
    FORMAT = MBTILES_MVT
    INTERACT = NONE
    MBTILES_MVT_APPLY_MVT_METADATA = NO
    MBTILES_MVT_CLIP = YES
    MBTILES_MVT_COORDINATE_SYSTEM_SOURCE = Source Data Bounds
    MBTILES_MVT_QUERY_FEATURE_TYPES_FOR_MERGE_FILTERS = Yes
    MBTILES_MVT_READER_META_ATTRIBUTES = fme_dataset fme_basename
    MBTILES_MVT_READ_BOOLEANS_AS_YES_NO = YES
    MBTILES_MVT_READ_NULLS = YES
    MBTILES_MVT_ZOOM_LEVEL = Maximum
    ORDER_RESULTS = No
    OUTPUT_FEATURES_DISPLAY = Schema and Data Features
    -> GeometryFilter
GeometryFilter
    FILTER_MODE = SIMPLE
    FILTER_MULTI = FILTER_TYPES]Area]FME_CONTROLLER_QUERY_FILE]]FME_CONTROLLER_CHOICE]Simple
    Area -> Counter
Counter
    CNT_ATTR = ID
    DOMAIN = counter
    SCOPE = Global
    START = 0
    -> AttributeRemover
AttributeRemover
    REMOVE_ATTRS = Name,Oppervlakte
    -> AttributeManager_27
    -> CenterPointReplacer_2
    -> CenterPointReplacer
    -> FeatureJoiner [LEFT]
    -> AttributeManager_8
    -> AttributeManager_7
Sampler_3 [off]
    RATE = 1
    SAMPLE_MODE = No
    SAMPLE_TYPE_LONG = First N Features
    SAMPLED -> AttributeManager
    NOT_SAMPLED -> Sampler_4
AttributeManager [off]
    ATTR_TABLE = SET_TO Name (buffer) = UberSquadra
Sampler_4 [off]
    RATE = 1
    SAMPLE_MODE = No
    SAMPLE_TYPE_LONG = First N Features
    SAMPLED -> AttributeManager_2
AttributeManager_2 [off]
    ATTR_TABLE = SET_TO Name (buffer) = UberSquadrino

Bookmark: Yardhino
CenterPointReplacer
    POINTTYPE = CENTER
    POINT -> NeighborFinder [CANDIDATE]
NeighborFinder
    CLOSE_LIST_ATTRS_TO_INCLUDE = ID
    CLOSE_LIST_ATTRS_TO_INCLUDE_MODE = Selected Attributes
    CLOSE_LIST_NAME = Neighbors
    INSERT_VERTEX = No
    K = 8
    MAX = 330
    MEASURES_FROM_CANDIDATE = No
    MEASURE_TYPE = Continuous
    MODE = Candidates Only
    TREAT_POLYGON_AS = Lines
    MATCHED -> ListElementCounter
ListElementCounter
    CNT_ATTR = _element_count
    LIST_NAME = Neighbors{}
    -> AttributeManager_4
AttributeManager_4
    ATTR_TABLE:
      REMOVE Neighbors{}.ID (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Neighbors{}.distance (real64)
      REMOVE Neighbors{}.angle (real64)
      REMOVE Neighbors{}.candidate_angle (real64)
      REMOVE Neighbors{}.candidate_label_angle (real64)
      REMOVE Neighbors{}.closest_candidate_x (real64)
      REMOVE Neighbors{}.closest_candidate_y (real64)
      REMOVE Neighbors{}.closest_base_x (real64)
      REMOVE Neighbors{}.closest_base_y (real64)
    -> Tester
Tester
    BOOL_OP = OR
    TEST_CLAUSE = TEST @Value(_element_count) = 4
    TEST_MODE = TEST
    PASSED -> FeatureJoiner [RIGHT]
FeatureJoiner
    ATTR_CONFLICT_RES = Prefer Left
    GEOMETRY_HANDLING = Prefer Left
    JOIN_KEYS = ID ID AUTO
    JOIN_MODE = Inner
    JOINED -> Dissolver
Dissolver
    ACCUM_INPUT_ATTRS = Drop Incoming Attributes
    CLEANING_TOLERANCE = Automatic
    CONNECT_Z_MODE = First Wins
    DEAGGREGATE_INPUT = Yes
    DIS_ATTR = Yardhino
    AREA -> Sorter_2
Sorter_2
    SORT_PARM = Yardhino NUMERIC DESCENDING
    SORTED -> Sampler_6
Note: 10 biggest Yards(hinos)
Sampler_6
    RATE = 10
    SAMPLE_MODE = No
    SAMPLE_TYPE_LONG = First N Features
    SAMPLED -> Yardhino (writer OGCKML_2)

Bookmark: input for loop
AttributeManager_8
    ATTR_TABLE = SET_TO Uber (uint64) = 1
    -> AttributeManager_9
AttributeManager_7
    ATTR_TABLE = RENAME_SET_VALUE ID > ID_Ref (int64)
    -> NeighborFinder_3 [CANDIDATE]
    -> FeatureJoiner_3 [LEFT]
    -> Junction
    -> NeighborFinder_6 [CANDIDATE]
    -> FeatureJoiner_6 [LEFT]
    -> FeatureJoiner_7 [LEFT]
    -> NeighborFinder_7 [CANDIDATE]
    -> Junction_18

Bookmark: This should be a loop - but dissolver blocks it _Uber 3
AttributeManager_9
    ATTR_TABLE = SET_TO Uber (uint64) = @sum(@Value(Uber),2)
    -> NeighborFinder_3 [BASE]
NeighborFinder_3
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_3
ListElementCounter_3
    CNT_ATTR = _element_count
    LIST_NAME = Finds{}
    -> Tester_4
Tester_4
    BOOL_OP = OR
    TEST_CLAUSE = TEST @Value(_element_count) = @Evaluate(@pow(@Value(Uber),2))
    TEST_MODE = TEST
    PASSED -> ListExploder_2
    FAILED -> AttributeManager_12
AttributeManager_12
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_13
ListExploder_2
    ATTR_ACCUM_MODE = Merge List Attributes
    ATTR_CONFLICT_RES = Use List Attribute Values
    INDEX_ATTR = _element_index
    LIST_ATTR = Finds{}
    ELEMENTS -> FeatureJoiner_3 [RIGHT]
FeatureJoiner_3
    ATTR_CONFLICT_RES = Prefer Left
    GEOMETRY_HANDLING = Prefer Left
    JOIN_KEYS = ID_Ref ID_Ref AUTO
    JOIN_MODE = Inner
    JOINED -> Dissolver_2
Dissolver_2
    ACCUM_INPUT_ATTRS = Drop Incoming Attributes
    CLEANING_TOLERANCE = Automatic
    CONNECT_Z_MODE = First Wins
    DEAGGREGATE_INPUT = Yes
    GROUP_BY = ID Uber
    AREA -> AttributeManager_13

Bookmark: This should be a loop - but dissolver blocks it _Uber 5
AttributeManager_13
    ATTR_TABLE = SET_TO Uber (uint64) = @sum(@Value(Uber),2)
    -> NeighborFinder_6 [BASE]
NeighborFinder_6
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_6
ListElementCounter_6
    CNT_ATTR = _element_count
    LIST_NAME = Finds{}
    -> Tester_8
Tester_8
    BOOL_OP = OR
    TEST_CLAUSE = TEST @Value(_element_count) = @Evaluate(@pow(@Value(Uber),2))
    TEST_MODE = TEST
    PASSED -> ListExploder_5
    FAILED -> AttributeManager_14
AttributeManager_14
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_13
ListExploder_5
    ATTR_ACCUM_MODE = Merge List Attributes
    ATTR_CONFLICT_RES = Use List Attribute Values
    INDEX_ATTR = _element_index
    LIST_ATTR = Finds{}
    ELEMENTS -> FeatureJoiner_6 [RIGHT]
FeatureJoiner_6
    ATTR_CONFLICT_RES = Prefer Left
    GEOMETRY_HANDLING = Prefer Left
    JOIN_KEYS = ID_Ref ID_Ref AUTO
    JOIN_MODE = Inner
    JOINED -> Dissolver_5
Dissolver_5
    ACCUM_INPUT_ATTRS = Drop Incoming Attributes
    CLEANING_TOLERANCE = Automatic
    CONNECT_Z_MODE = First Wins
    DEAGGREGATE_INPUT = Yes
    GROUP_BY = ID Uber
    AREA -> AttributeManager_15

Bookmark: This should be a loop - but dissolver blocks it _Uber 7
AttributeManager_15
    ATTR_TABLE = SET_TO Uber (uint64) = @sum(@Value(Uber),2)
    -> NeighborFinder_7 [BASE]
NeighborFinder_7
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_7
ListElementCounter_7
    CNT_ATTR = _element_count
    LIST_NAME = Finds{}
    -> Tester_9
Tester_9
    BOOL_OP = OR
    TEST_CLAUSE = TEST @Value(_element_count) = @Evaluate(@pow(@Value(Uber),2))
    TEST_MODE = TEST
    PASSED -> ListExploder_6
    FAILED -> AttributeManager_16
AttributeManager_16
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_13
ListExploder_6
    ATTR_ACCUM_MODE = Merge List Attributes
    ATTR_CONFLICT_RES = Use List Attribute Values
    INDEX_ATTR = _element_index
    LIST_ATTR = Finds{}
    ELEMENTS -> FeatureJoiner_7 [RIGHT]
FeatureJoiner_7
    ATTR_CONFLICT_RES = Prefer Left
    GEOMETRY_HANDLING = Prefer Left
    JOIN_KEYS = ID_Ref ID_Ref AUTO
    JOIN_MODE = Inner
    JOINED -> Dissolver_6
Dissolver_6
    ACCUM_INPUT_ATTRS = Drop Incoming Attributes
    CLEANING_TOLERANCE = Automatic
    CONNECT_Z_MODE = First Wins
    DEAGGREGATE_INPUT = Yes
    GROUP_BY = ID Uber
    AREA -> AttributeManager_10

Bookmark: This should be a loop - but dissolver blocks it _Uber 9
AttributeManager_10
    ATTR_TABLE = SET_TO Uber (uint64) = @sum(@Value(Uber),2)
    -> NeighborFinder_4 [BASE]
NeighborFinder_4
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_4
ListElementCounter_4
    CNT_ATTR = _element_count
    LIST_NAME = Finds{}
    -> Tester_5
Tester_5
    BOOL_OP = OR
    TEST_CLAUSE = TEST @Value(_element_count) = @Evaluate(@pow(@Value(Uber),2))
    TEST_MODE = TEST
    PASSED -> ListExploder_3
    FAILED -> AttributeManager_11
AttributeManager_11
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_12
ListExploder_3
    ATTR_ACCUM_MODE = Merge List Attributes
    ATTR_CONFLICT_RES = Use List Attribute Values
    INDEX_ATTR = _element_index
    LIST_ATTR = Finds{}
    ELEMENTS -> FeatureJoiner_4 [RIGHT]
FeatureJoiner_4
    ATTR_CONFLICT_RES = Prefer Left
    GEOMETRY_HANDLING = Prefer Left
    JOIN_KEYS = ID_Ref ID_Ref AUTO
    JOIN_MODE = Inner
    JOINED -> Dissolver_3
Dissolver_3
    ACCUM_INPUT_ATTRS = Drop Incoming Attributes
    CLEANING_TOLERANCE = Automatic
    CONNECT_Z_MODE = First Wins
    DEAGGREGATE_INPUT = Yes
    GROUP_BY = ID Uber
    AREA -> AttributeManager_17

Bookmark: This should be a loop - but dissolver blocks it _Uber 11
AttributeManager_17
    ATTR_TABLE = SET_TO Uber (uint64) = @sum(@Value(Uber),2)
    -> NeighborFinder_5 [BASE]
NeighborFinder_5
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_5
ListElementCounter_5
    CNT_ATTR = _element_count
    LIST_NAME = Finds{}
    -> Tester_6
Tester_6
    BOOL_OP = OR
    TEST_CLAUSE = TEST @Value(_element_count) = @Evaluate(@pow(@Value(Uber),2))
    TEST_MODE = TEST
    PASSED -> ListExploder_4
    FAILED -> AttributeManager_18
AttributeManager_18
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_12
ListExploder_4
    ATTR_ACCUM_MODE = Merge List Attributes
    ATTR_CONFLICT_RES = Use List Attribute Values
    INDEX_ATTR = _element_index
    LIST_ATTR = Finds{}
    ELEMENTS -> FeatureJoiner_5 [RIGHT]
FeatureJoiner_5
    ATTR_CONFLICT_RES = Prefer Left
    GEOMETRY_HANDLING = Prefer Left
    JOIN_KEYS = ID_Ref ID_Ref AUTO
    JOIN_MODE = Inner
    JOINED -> Dissolver_4
Dissolver_4
    ACCUM_INPUT_ATTRS = Drop Incoming Attributes
    CLEANING_TOLERANCE = Automatic
    CONNECT_Z_MODE = First Wins
    DEAGGREGATE_INPUT = Yes
    GROUP_BY = ID Uber
    AREA -> AttributeManager_19

Bookmark: This should be a loop - but dissolver blocks it _Uber 13
AttributeManager_19
    ATTR_TABLE = SET_TO Uber (uint64) = @sum(@Value(Uber),2)
    -> NeighborFinder_8 [BASE]
NeighborFinder_8
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_8
ListElementCounter_8
    CNT_ATTR = _element_count
    LIST_NAME = Finds{}
    -> Tester_10
Tester_10
    BOOL_OP = OR
    TEST_CLAUSE = TEST @Value(_element_count) = @Evaluate(@pow(@Value(Uber),2))
    TEST_MODE = TEST
    PASSED -> ListExploder_7
    FAILED -> AttributeManager_20
AttributeManager_20
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_12
ListExploder_7
    ATTR_ACCUM_MODE = Merge List Attributes
    ATTR_CONFLICT_RES = Use List Attribute Values
    INDEX_ATTR = _element_index
    LIST_ATTR = Finds{}
    ELEMENTS -> FeatureJoiner_8 [RIGHT]
FeatureJoiner_8
    ATTR_CONFLICT_RES = Prefer Left
    GEOMETRY_HANDLING = Prefer Left
    JOIN_KEYS = ID_Ref ID_Ref AUTO
    JOIN_MODE = Inner
    JOINED -> Dissolver_7
Dissolver_7
    ACCUM_INPUT_ATTRS = Drop Incoming Attributes
    CLEANING_TOLERANCE = Automatic
    CONNECT_Z_MODE = First Wins
    DEAGGREGATE_INPUT = Yes
    GROUP_BY = ID Uber
    AREA -> AttributeManager_21

Bookmark: This should be a loop - but dissolver blocks it _Uber 15
AttributeManager_21
    ATTR_TABLE = SET_TO Uber (uint64) = @sum(@Value(Uber),2)
    -> NeighborFinder_9 [BASE]
NeighborFinder_9
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_9
ListElementCounter_9
    CNT_ATTR = _element_count
    LIST_NAME = Finds{}
    -> Tester_11
Tester_11
    BOOL_OP = OR
    TEST_CLAUSE = TEST @Value(_element_count) = @Evaluate(@pow(@Value(Uber),2))
    TEST_MODE = TEST
    PASSED -> ListExploder_8
    FAILED -> AttributeManager_22
AttributeManager_22
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_11
ListExploder_8
    ATTR_ACCUM_MODE = Merge List Attributes
    ATTR_CONFLICT_RES = Use List Attribute Values
    INDEX_ATTR = _element_index
    LIST_ATTR = Finds{}
    ELEMENTS -> FeatureJoiner_9 [RIGHT]
FeatureJoiner_9
    ATTR_CONFLICT_RES = Prefer Left
    GEOMETRY_HANDLING = Prefer Left
    JOIN_KEYS = ID_Ref ID_Ref AUTO
    JOIN_MODE = Inner
    JOINED -> Dissolver_8
Dissolver_8
    ACCUM_INPUT_ATTRS = Drop Incoming Attributes
    CLEANING_TOLERANCE = Automatic
    CONNECT_Z_MODE = First Wins
    DEAGGREGATE_INPUT = Yes
    GROUP_BY = ID Uber
    AREA -> AttributeManager_23

Bookmark: This should be a loop - but dissolver blocks it _Uber 17
AttributeManager_23
    ATTR_TABLE = SET_TO Uber (uint64) = @sum(@Value(Uber),2)
    -> NeighborFinder_10 [BASE]
NeighborFinder_10
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_10
ListElementCounter_10
    CNT_ATTR = _element_count
    LIST_NAME = Finds{}
    -> Tester_12
Tester_12
    BOOL_OP = OR
    TEST_CLAUSE = TEST @Value(_element_count) = @Evaluate(@pow(@Value(Uber),2))
    TEST_MODE = TEST
    PASSED -> ListExploder_9
    FAILED -> AttributeManager_24
AttributeManager_24
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_11
ListExploder_9
    ATTR_ACCUM_MODE = Merge List Attributes
    ATTR_CONFLICT_RES = Use List Attribute Values
    INDEX_ATTR = _element_index
    LIST_ATTR = Finds{}
    ELEMENTS -> FeatureJoiner_10 [RIGHT]
FeatureJoiner_10
    ATTR_CONFLICT_RES = Prefer Left
    GEOMETRY_HANDLING = Prefer Left
    JOIN_KEYS = ID_Ref ID_Ref AUTO
    JOIN_MODE = Inner
    JOINED -> Dissolver_9
Dissolver_9
    ACCUM_INPUT_ATTRS = Drop Incoming Attributes
    CLEANING_TOLERANCE = Automatic
    CONNECT_Z_MODE = First Wins
    DEAGGREGATE_INPUT = Yes
    GROUP_BY = ID Uber
    AREA -> AttributeManager_25

Bookmark: This should be a loop - but dissolver blocks it _Uber 19
AttributeManager_25
    ATTR_TABLE = SET_TO Uber (uint64) = @sum(@Value(Uber),2)
    -> NeighborFinder_11 [BASE]
NeighborFinder_11
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_11
ListElementCounter_11
    CNT_ATTR = _element_count
    LIST_NAME = Finds{}
    -> Tester_13
Tester_13
    BOOL_OP = OR
    TEST_CLAUSE = TEST @Value(_element_count) = @Evaluate(@pow(@Value(Uber),2))
    TEST_MODE = TEST
    PASSED -> ListExploder_10
    FAILED -> AttributeManager_26
AttributeManager_26
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_11
ListExploder_10
    ATTR_ACCUM_MODE = Merge List Attributes
    ATTR_CONFLICT_RES = Use List Attribute Values
    INDEX_ATTR = _element_index
    LIST_ATTR = Finds{}
    ELEMENTS -> FeatureJoiner_11 [RIGHT]
FeatureJoiner_11
    ATTR_CONFLICT_RES = Prefer Left
    GEOMETRY_HANDLING = Prefer Left
    JOIN_KEYS = ID_Ref ID_Ref AUTO
    JOIN_MODE = Inner
    JOINED -> Dissolver_10
Dissolver_10
    ACCUM_INPUT_ATTRS = Drop Incoming Attributes
    CLEANING_TOLERANCE = Automatic
    CONNECT_Z_MODE = First Wins
    DEAGGREGATE_INPUT = Yes
    GROUP_BY = ID Uber
    AREA -> AttributeManager_30

Bookmark: This should be a loop - but dissolver blocks it _Uber 21
AttributeManager_30
    ATTR_TABLE = SET_TO Uber (uint64) = @sum(@Value(Uber),2)
    -> NeighborFinder_13 [BASE]
NeighborFinder_13
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_13
ListElementCounter_13
    CNT_ATTR = _element_count
    LIST_NAME = Finds{}
    -> Tester_16
Tester_16
    BOOL_OP = OR
    TEST_CLAUSE = TEST @Value(_element_count) = @Evaluate(@pow(@Value(Uber),2))
    TEST_MODE = TEST
    PASSED -> ListExploder_12
    FAILED -> AttributeManager_31
AttributeManager_31
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_10
ListExploder_12
    ATTR_ACCUM_MODE = Merge List Attributes
    ATTR_CONFLICT_RES = Use List Attribute Values
    INDEX_ATTR = _element_index
    LIST_ATTR = Finds{}
    ELEMENTS -> FeatureJoiner_13 [RIGHT]
FeatureJoiner_13
    ATTR_CONFLICT_RES = Prefer Left
    GEOMETRY_HANDLING = Prefer Left
    JOIN_KEYS = ID_Ref ID_Ref AUTO
    JOIN_MODE = Inner
    JOINED -> Dissolver_11
Dissolver_11
    ACCUM_INPUT_ATTRS = Drop Incoming Attributes
    CLEANING_TOLERANCE = Automatic
    CONNECT_Z_MODE = First Wins
    DEAGGREGATE_INPUT = Yes
    GROUP_BY = ID Uber
    AREA -> AttributeManager_32

Bookmark: This should be a loop - but dissolver blocks it _Uber 23
AttributeManager_32
    ATTR_TABLE = SET_TO Uber (uint64) = @sum(@Value(Uber),2)
    -> NeighborFinder_14 [BASE]
NeighborFinder_14
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_14
ListElementCounter_14
    CNT_ATTR = _element_count
    LIST_NAME = Finds{}
    -> Tester_17
Tester_17
    BOOL_OP = OR
    TEST_CLAUSE = TEST @Value(_element_count) = @Evaluate(@pow(@Value(Uber),2))
    TEST_MODE = TEST
    PASSED -> ListExploder_13
    FAILED -> AttributeManager_33
AttributeManager_33
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_10
ListExploder_13
    ATTR_ACCUM_MODE = Merge List Attributes
    ATTR_CONFLICT_RES = Use List Attribute Values
    INDEX_ATTR = _element_index
    LIST_ATTR = Finds{}
    ELEMENTS -> FeatureJoiner_14 [RIGHT]
FeatureJoiner_14
    ATTR_CONFLICT_RES = Prefer Left
    GEOMETRY_HANDLING = Prefer Left
    JOIN_KEYS = ID_Ref ID_Ref AUTO
    JOIN_MODE = Inner
    JOINED -> Dissolver_12
Dissolver_12
    ACCUM_INPUT_ATTRS = Drop Incoming Attributes
    CLEANING_TOLERANCE = Automatic
    CONNECT_Z_MODE = First Wins
    DEAGGREGATE_INPUT = Yes
    GROUP_BY = ID Uber
    AREA -> AttributeManager_34

Bookmark: This should be a loop - but dissolver blocks it _Uber 25
AttributeManager_34
    ATTR_TABLE = SET_TO Uber (uint64) = @sum(@Value(Uber),2)
    -> NeighborFinder_15 [BASE]
NeighborFinder_15
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_15
ListElementCounter_15
    CNT_ATTR = _element_count
    LIST_NAME = Finds{}
    -> Tester_18
Tester_18
    BOOL_OP = OR
    TEST_CLAUSE = TEST @Value(_element_count) = @Evaluate(@pow(@Value(Uber),2))
    TEST_MODE = TEST
    PASSED -> ListExploder_14
    FAILED -> AttributeManager_35
AttributeManager_35
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_10
ListExploder_14
    ATTR_ACCUM_MODE = Merge List Attributes
    ATTR_CONFLICT_RES = Use List Attribute Values
    INDEX_ATTR = _element_index
    LIST_ATTR = Finds{}
    ELEMENTS -> FeatureJoiner_15 [RIGHT]
FeatureJoiner_15
    ATTR_CONFLICT_RES = Prefer Left
    GEOMETRY_HANDLING = Prefer Left
    JOIN_KEYS = ID_Ref ID_Ref AUTO
    JOIN_MODE = Inner
    JOINED -> Dissolver_13
Dissolver_13
    ACCUM_INPUT_ATTRS = Drop Incoming Attributes
    CLEANING_TOLERANCE = Automatic
    CONNECT_Z_MODE = First Wins
    DEAGGREGATE_INPUT = Yes
    GROUP_BY = ID Uber
    AREA -> AttributeManager_36

Bookmark: This should be a loop - but dissolver blocks it _Uber 27
AttributeManager_36
    ATTR_TABLE = SET_TO Uber (uint64) = @sum(@Value(Uber),2)
    -> NeighborFinder_16 [BASE]
NeighborFinder_16
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_16
ListElementCounter_16
    CNT_ATTR = _element_count
    LIST_NAME = Finds{}
    -> Tester_19
Tester_19
    BOOL_OP = OR
    TEST_CLAUSE = TEST @Value(_element_count) = @Evaluate(@pow(@Value(Uber),2))
    TEST_MODE = TEST
    PASSED -> ListExploder_15
    FAILED -> AttributeManager_37
AttributeManager_37
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_9
ListExploder_15
    ATTR_ACCUM_MODE = Merge List Attributes
    ATTR_CONFLICT_RES = Use List Attribute Values
    INDEX_ATTR = _element_index
    LIST_ATTR = Finds{}
    ELEMENTS -> FeatureJoiner_16 [RIGHT]
FeatureJoiner_16
    ATTR_CONFLICT_RES = Prefer Left
    GEOMETRY_HANDLING = Prefer Left
    JOIN_KEYS = ID_Ref ID_Ref AUTO
    JOIN_MODE = Inner
    JOINED -> Dissolver_14
Dissolver_14
    ACCUM_INPUT_ATTRS = Drop Incoming Attributes
    CLEANING_TOLERANCE = Automatic
    CONNECT_Z_MODE = First Wins
    DEAGGREGATE_INPUT = Yes
    GROUP_BY = ID Uber
    AREA -> AttributeManager_38

Bookmark: This should be a loop - but dissolver blocks it _Uber 29
AttributeManager_38
    ATTR_TABLE = SET_TO Uber (uint64) = @sum(@Value(Uber),2)
    -> NeighborFinder_17 [BASE]
NeighborFinder_17
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_17
ListElementCounter_17
    CNT_ATTR = _element_count
    LIST_NAME = Finds{}
    -> Tester_20
Tester_20
    BOOL_OP = OR
    TEST_CLAUSE = TEST @Value(_element_count) = @Evaluate(@pow(@Value(Uber),2))
    TEST_MODE = TEST
    PASSED -> ListExploder_16
    FAILED -> AttributeManager_39
AttributeManager_39
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_9
ListExploder_16
    ATTR_ACCUM_MODE = Merge List Attributes
    ATTR_CONFLICT_RES = Use List Attribute Values
    INDEX_ATTR = _element_index
    LIST_ATTR = Finds{}
    ELEMENTS -> FeatureJoiner_17 [RIGHT]
FeatureJoiner_17
    ATTR_CONFLICT_RES = Prefer Left
    GEOMETRY_HANDLING = Prefer Left
    JOIN_KEYS = ID_Ref ID_Ref AUTO
    JOIN_MODE = Inner
    JOINED -> Dissolver_15
Dissolver_15
    ACCUM_INPUT_ATTRS = Drop Incoming Attributes
    CLEANING_TOLERANCE = Automatic
    CONNECT_Z_MODE = First Wins
    DEAGGREGATE_INPUT = Yes
    GROUP_BY = ID Uber
    AREA -> AttributeManager_40

Bookmark: This should be a loop - but dissolver blocks it _Uber 31
AttributeManager_40
    ATTR_TABLE = SET_TO Uber (uint64) = @sum(@Value(Uber),2)
    -> NeighborFinder_18 [BASE]
NeighborFinder_18
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_18
ListElementCounter_18
    CNT_ATTR = _element_count
    LIST_NAME = Finds{}
    -> Tester_21
Tester_21
    BOOL_OP = OR
    TEST_CLAUSE = TEST @Value(_element_count) = @Evaluate(@pow(@Value(Uber),2))
    TEST_MODE = TEST
    PASSED -> ListExploder_17
    FAILED -> AttributeManager_41
AttributeManager_41
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_9
ListExploder_17
    ATTR_ACCUM_MODE = Merge List Attributes
    ATTR_CONFLICT_RES = Use List Attribute Values
    INDEX_ATTR = _element_index
    LIST_ATTR = Finds{}
    ELEMENTS -> FeatureJoiner_18 [RIGHT]
FeatureJoiner_18
    ATTR_CONFLICT_RES = Prefer Left
    GEOMETRY_HANDLING = Prefer Left
    JOIN_KEYS = ID_Ref ID_Ref AUTO
    JOIN_MODE = Inner
    JOINED -> Dissolver_16
Dissolver_16
    ACCUM_INPUT_ATTRS = Drop Incoming Attributes
    CLEANING_TOLERANCE = Automatic
    CONNECT_Z_MODE = First Wins
    DEAGGREGATE_INPUT = Yes
    GROUP_BY = ID Uber
    AREA -> AttributeManager_42

Bookmark: This should be a loop - but dissolver blocks it _Uber 33
AttributeManager_42
    ATTR_TABLE = SET_TO Uber (uint64) = @sum(@Value(Uber),2)
    -> NeighborFinder_19 [BASE]
NeighborFinder_19
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_19
ListElementCounter_19
    CNT_ATTR = _element_count
    LIST_NAME = Finds{}
    -> Tester_22
Tester_22
    BOOL_OP = OR
    TEST_CLAUSE = TEST @Value(_element_count) = @Evaluate(@pow(@Value(Uber),2))
    TEST_MODE = TEST
    PASSED -> ListExploder_18
    FAILED -> AttributeManager_43
AttributeManager_43
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_4
ListExploder_18
    ATTR_ACCUM_MODE = Merge List Attributes
    ATTR_CONFLICT_RES = Use List Attribute Values
    INDEX_ATTR = _element_index
    LIST_ATTR = Finds{}
    ELEMENTS -> FeatureJoiner_19 [RIGHT]
FeatureJoiner_19
    ATTR_CONFLICT_RES = Prefer Left
    GEOMETRY_HANDLING = Prefer Left
    JOIN_KEYS = ID_Ref ID_Ref AUTO
    JOIN_MODE = Inner
    JOINED -> Dissolver_17
Dissolver_17
    ACCUM_INPUT_ATTRS = Drop Incoming Attributes
    CLEANING_TOLERANCE = Automatic
    CONNECT_Z_MODE = First Wins
    DEAGGREGATE_INPUT = Yes
    GROUP_BY = ID Uber
    AREA -> AttributeManager_44

Bookmark: This should be a loop - but dissolver blocks it _Uber 35
AttributeManager_44
    ATTR_TABLE = SET_TO Uber (uint64) = @sum(@Value(Uber),2)
    -> NeighborFinder_20 [BASE]
NeighborFinder_20
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_20
ListElementCounter_20
    CNT_ATTR = _element_count
    LIST_NAME = Finds{}
    -> Tester_23
Tester_23
    BOOL_OP = OR
    TEST_CLAUSE = TEST @Value(_element_count) = @Evaluate(@pow(@Value(Uber),2))
    TEST_MODE = TEST
    PASSED -> ListExploder_19
    FAILED -> AttributeManager_45
AttributeManager_45
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_4
ListExploder_19
    ATTR_ACCUM_MODE = Merge List Attributes
    ATTR_CONFLICT_RES = Use List Attribute Values
    INDEX_ATTR = _element_index
    LIST_ATTR = Finds{}
    ELEMENTS -> FeatureJoiner_20 [RIGHT]
FeatureJoiner_20
    ATTR_CONFLICT_RES = Prefer Left
    GEOMETRY_HANDLING = Prefer Left
    JOIN_KEYS = ID_Ref ID_Ref AUTO
    JOIN_MODE = Inner
    JOINED -> Dissolver_18
Dissolver_18
    ACCUM_INPUT_ATTRS = Drop Incoming Attributes
    CLEANING_TOLERANCE = Automatic
    CONNECT_Z_MODE = First Wins
    DEAGGREGATE_INPUT = Yes
    GROUP_BY = ID Uber
    AREA -> AttributeManager_46

Bookmark: This should be a loop - but dissolver blocks it _Uber 37
AttributeManager_46
    ATTR_TABLE = SET_TO Uber (uint64) = @sum(@Value(Uber),2)
    -> NeighborFinder_21 [BASE]
NeighborFinder_21
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_21
ListElementCounter_21
    CNT_ATTR = _element_count
    LIST_NAME = Finds{}
    -> Tester_24
Tester_24
    BOOL_OP = OR
    TEST_CLAUSE = TEST @Value(_element_count) = @Evaluate(@pow(@Value(Uber),2))
    TEST_MODE = TEST
    PASSED -> ListExploder_20
    FAILED -> AttributeManager_47
AttributeManager_47
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_4
ListExploder_20
    ATTR_ACCUM_MODE = Merge List Attributes
    ATTR_CONFLICT_RES = Use List Attribute Values
    INDEX_ATTR = _element_index
    LIST_ATTR = Finds{}
    ELEMENTS -> FeatureJoiner_21 [RIGHT]
FeatureJoiner_21
    ATTR_CONFLICT_RES = Prefer Left
    GEOMETRY_HANDLING = Prefer Left
    JOIN_KEYS = ID_Ref ID_Ref AUTO
    JOIN_MODE = Inner
    JOINED -> Dissolver_19
Dissolver_19
    ACCUM_INPUT_ATTRS = Drop Incoming Attributes
    CLEANING_TOLERANCE = Automatic
    CONNECT_Z_MODE = First Wins
    DEAGGREGATE_INPUT = Yes
    GROUP_BY = ID Uber
    AREA -> Junction_4

Bookmark: Ubersquadrino - 2² - to create 2 by 2 starting square
CenterPointReplacer_2
    POINTTYPE = CENTER
    POINT -> NeighborFinder_2 [BASE]
    POINT -> AttributeManager_6
AttributeManager_6
    ATTR_TABLE = RENAME_SET_VALUE ID > ID_Ref (int64)
    -> NeighborFinder_2 [CANDIDATE]
NeighborFinder_2
    CANDIDATES_FIRST = No
    CLOSE_LIST_ATTRS_TO_INCLUDE = ID_Ref
    CLOSE_LIST_ATTRS_TO_INCLUDE_MODE = Selected Attributes
    CLOSE_LIST_NAME = Neighbors
    INSERT_VERTEX = No
    K = 8
    MAX = 330
    MEASURES_FROM_CANDIDATE = No
    MEASURE_TYPE = Continuous
    MODE = Bases and Candidates
    TREAT_POLYGON_AS = Lines
    MATCHED -> ListElementCounter_2
ListElementCounter_2
    CNT_ATTR = _element_count
    LIST_NAME = Neighbors{}
    -> ListExploder
ListExploder
    ATTR_ACCUM_MODE = Merge List Attributes
    ATTR_CONFLICT_RES = Use List Attribute Values
    INDEX_ATTR = _element_index
    LIST_ATTR = Neighbors{}
    ELEMENTS -> Tester_3
Tester_3
    BOOL_OP = OR
    TEST_CLAUSE = TEST @Value(angle) = 0
    TEST_MODE = TEST
    PASSED -> FeatureJoiner_2 [LEFT]
AttributeManager_27
    ATTR_TABLE = RENAME_SET_VALUE ID > ID_Ref (int64)
    -> FeatureJoiner_2 [RIGHT]
FeatureJoiner_2
    ATTR_CONFLICT_RES = Prefer Left
    GEOMETRY_HANDLING = Prefer Right
    JOIN_KEYS = ID_Ref ID_Ref AUTO
    JOIN_MODE = Inner
    JOINED -> Aggregator
Aggregator
    ACCUM_ATTRS_NAME = Drop Incoming Attributes
    AGGREGATE_TYPE = Homogeneous Collection (If Possible)
    COUNT_ATTR = Uber
    GROUP_BY = ID
    MODE = Geometry - Assemble One Level
    SEP = ,
    AGGREGATE -> Tester_2
Tester_2
    BOOL_OP = OR
    TEST_CLAUSE = TEST @Value(Uber) = 2
    TEST_MODE = TEST
    PASSED -> AttributeManager_29
    PASSED -> CenterPointReplacer_3
CenterPointReplacer_3
    POINTTYPE = CENTER
    POINT -> NeighborFinder_12 [BASE]
    POINT -> AttributeManager_28
AttributeManager_28
    ATTR_TABLE = RENAME_SET_VALUE ID > ID_Ref (int64)
    -> NeighborFinder_12 [CANDIDATE]
NeighborFinder_12
    CANDIDATES_FIRST = No
    CLOSE_LIST_ATTRS_TO_INCLUDE = ID_Ref
    CLOSE_LIST_ATTRS_TO_INCLUDE_MODE = Selected Attributes
    CLOSE_LIST_NAME = Neighbors
    INSERT_VERTEX = No
    K = 8
    MAX = 330
    MEASURES_FROM_CANDIDATE = No
    MEASURE_TYPE = Continuous
    MODE = Bases and Candidates
    TREAT_POLYGON_AS = Lines
    MATCHED -> ListElementCounter_12
ListElementCounter_12
    CNT_ATTR = _element_count
    LIST_NAME = Neighbors{}
    -> ListExploder_11
ListExploder_11
    ATTR_ACCUM_MODE = Merge List Attributes
    ATTR_CONFLICT_RES = Use List Attribute Values
    INDEX_ATTR = _element_index
    LIST_ATTR = Neighbors{}
    ELEMENTS -> Tester_14
Tester_14
    BOOL_OP = OR
    TEST_CLAUSE:
      TEST @Value(angle) = 270
      TEST @Value(ID) = @Value(ID_Ref)
    TEST_MODE = TEST
    PASSED -> FeatureJoiner_12 [LEFT]
AttributeManager_29
    ATTR_TABLE = RENAME_SET_VALUE ID > ID_Ref (int64)
    -> FeatureJoiner_12 [RIGHT]
FeatureJoiner_12
    ATTR_CONFLICT_RES = Prefer Left
    GEOMETRY_HANDLING = Prefer Right
    JOIN_KEYS = ID_Ref ID_Ref AUTO
    JOIN_MODE = Inner
    JOINED -> Aggregator_2
Aggregator_2
    ACCUM_ATTRS_NAME = Drop Incoming Attributes
    AGGREGATE_TYPE = Homogeneous Collection (If Possible)
    COUNT_ATTR = Uber
    GROUP_BY = ID
    MODE = Geometry - Assemble One Level
    SEP = ,
    AGGREGATE -> Tester_15
Tester_15
    BOOL_OP = OR
    TEST_CLAUSE = TEST @Value(Uber) = 2
    TEST_MODE = TEST
    PASSED -> AttributeManager_50

Bookmark: This should be a loop - but dissolver blocks it _Uber 4
AttributeManager_50
    ATTR_TABLE = SET_TO Uber (uint64) = @sum(@Value(Uber),2)
    -> NeighborFinder_22 [BASE]
NeighborFinder_22
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_22
ListElementCounter_22
    CNT_ATTR = _element_count
    LIST_NAME = Finds{}
    -> Tester_25
Tester_25
    BOOL_OP = OR
    TEST_CLAUSE = TEST @Value(_element_count) = @Evaluate(@pow(@Value(Uber),2))
    TEST_MODE = TEST
    PASSED -> ListExploder_21
    FAILED -> AttributeManager_51
AttributeManager_51
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_14
ListExploder_21
    ATTR_ACCUM_MODE = Merge List Attributes
    ATTR_CONFLICT_RES = Use List Attribute Values
    INDEX_ATTR = _element_index
    LIST_ATTR = Finds{}
    ELEMENTS -> FeatureJoiner_22 [RIGHT]
FeatureJoiner_22
    ATTR_CONFLICT_RES = Prefer Left
    GEOMETRY_HANDLING = Prefer Left
    JOIN_KEYS = ID_Ref ID_Ref AUTO
    JOIN_MODE = Inner
    JOINED -> Dissolver_20
Dissolver_20
    ACCUM_INPUT_ATTRS = Drop Incoming Attributes
    CLEANING_TOLERANCE = Automatic
    CONNECT_Z_MODE = First Wins
    DEAGGREGATE_INPUT = Yes
    GROUP_BY = ID Uber
    AREA -> AttributeManager_52

Bookmark: This should be a loop - but dissolver blocks it _Uber 6
AttributeManager_52
    ATTR_TABLE = SET_TO Uber (uint64) = @sum(@Value(Uber),2)
    -> NeighborFinder_23 [BASE]
NeighborFinder_23
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_23
ListElementCounter_23
    CNT_ATTR = _element_count
    LIST_NAME = Finds{}
    -> Tester_26
Tester_26
    BOOL_OP = OR
    TEST_CLAUSE = TEST @Value(_element_count) = @Evaluate(@pow(@Value(Uber),2))
    TEST_MODE = TEST
    PASSED -> ListExploder_22
    FAILED -> AttributeManager_53
AttributeManager_53
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_14
ListExploder_22
    ATTR_ACCUM_MODE = Merge List Attributes
    ATTR_CONFLICT_RES = Use List Attribute Values
    INDEX_ATTR = _element_index
    LIST_ATTR = Finds{}
    ELEMENTS -> FeatureJoiner_23 [RIGHT]
FeatureJoiner_23
    ATTR_CONFLICT_RES = Prefer Left
    GEOMETRY_HANDLING = Prefer Left
    JOIN_KEYS = ID_Ref ID_Ref AUTO
    JOIN_MODE = Inner
    JOINED -> Dissolver_21
Dissolver_21
    ACCUM_INPUT_ATTRS = Drop Incoming Attributes
    CLEANING_TOLERANCE = Automatic
    CONNECT_Z_MODE = First Wins
    DEAGGREGATE_INPUT = Yes
    GROUP_BY = ID Uber
    AREA -> AttributeManager_54

Bookmark: This should be a loop - but dissolver blocks it _Uber 8
AttributeManager_54
    ATTR_TABLE = SET_TO Uber (uint64) = @sum(@Value(Uber),2)
    -> NeighborFinder_24 [BASE]
NeighborFinder_24
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_24
ListElementCounter_24
    CNT_ATTR = _element_count
    LIST_NAME = Finds{}
    -> Tester_27
Tester_27
    BOOL_OP = OR
    TEST_CLAUSE = TEST @Value(_element_count) = @Evaluate(@pow(@Value(Uber),2))
    TEST_MODE = TEST
    PASSED -> ListExploder_23
    FAILED -> AttributeManager_55
AttributeManager_55
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_14
ListExploder_23
    ATTR_ACCUM_MODE = Merge List Attributes
    ATTR_CONFLICT_RES = Use List Attribute Values
    INDEX_ATTR = _element_index
    LIST_ATTR = Finds{}
    ELEMENTS -> FeatureJoiner_24 [RIGHT]
FeatureJoiner_24
    ATTR_CONFLICT_RES = Prefer Left
    GEOMETRY_HANDLING = Prefer Left
    JOIN_KEYS = ID_Ref ID_Ref AUTO
    JOIN_MODE = Inner
    JOINED -> Dissolver_22
Dissolver_22
    ACCUM_INPUT_ATTRS = Drop Incoming Attributes
    CLEANING_TOLERANCE = Automatic
    CONNECT_Z_MODE = First Wins
    DEAGGREGATE_INPUT = Yes
    GROUP_BY = ID Uber
    AREA -> AttributeManager_56

Bookmark: This should be a loop - but dissolver blocks it _Uber 10
AttributeManager_56
    ATTR_TABLE = SET_TO Uber (uint64) = @sum(@Value(Uber),2)
    -> NeighborFinder_25 [BASE]
NeighborFinder_25
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_25
ListElementCounter_25
    CNT_ATTR = _element_count
    LIST_NAME = Finds{}
    -> Tester_28
Tester_28
    BOOL_OP = OR
    TEST_CLAUSE = TEST @Value(_element_count) = @Evaluate(@pow(@Value(Uber),2))
    TEST_MODE = TEST
    PASSED -> ListExploder_24
    FAILED -> AttributeManager_57
AttributeManager_57
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_14
ListExploder_24
    ATTR_ACCUM_MODE = Merge List Attributes
    ATTR_CONFLICT_RES = Use List Attribute Values
    INDEX_ATTR = _element_index
    LIST_ATTR = Finds{}
    ELEMENTS -> FeatureJoiner_25 [RIGHT]
FeatureJoiner_25
    ATTR_CONFLICT_RES = Prefer Left
    GEOMETRY_HANDLING = Prefer Left
    JOIN_KEYS = ID_Ref ID_Ref AUTO
    JOIN_MODE = Inner
    JOINED -> Dissolver_23
Dissolver_23
    ACCUM_INPUT_ATTRS = Drop Incoming Attributes
    CLEANING_TOLERANCE = Automatic
    CONNECT_Z_MODE = First Wins
    DEAGGREGATE_INPUT = Yes
    GROUP_BY = ID Uber
    AREA -> AttributeManager_49

Bookmark: This should be a loop - but dissolver blocks it _Uber 12
AttributeManager_49
    ATTR_TABLE = SET_TO Uber (uint64) = @sum(@Value(Uber),2)
    -> NeighborFinder_26 [BASE]
NeighborFinder_26
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_26
ListElementCounter_26
    CNT_ATTR = _element_count
    LIST_NAME = Finds{}
    -> Tester_29
Tester_29
    BOOL_OP = OR
    TEST_CLAUSE = TEST @Value(_element_count) = @Evaluate(@pow(@Value(Uber),2))
    TEST_MODE = TEST
    PASSED -> ListExploder_25
    FAILED -> AttributeManager_58
AttributeManager_58
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_17
ListExploder_25
    ATTR_ACCUM_MODE = Merge List Attributes
    ATTR_CONFLICT_RES = Use List Attribute Values
    INDEX_ATTR = _element_index
    LIST_ATTR = Finds{}
    ELEMENTS -> FeatureJoiner_26 [RIGHT]
FeatureJoiner_26
    ATTR_CONFLICT_RES = Prefer Left
    GEOMETRY_HANDLING = Prefer Left
    JOIN_KEYS = ID_Ref ID_Ref AUTO
    JOIN_MODE = Inner
    JOINED -> Dissolver_24
Dissolver_24
    ACCUM_INPUT_ATTRS = Drop Incoming Attributes
    CLEANING_TOLERANCE = Automatic
    CONNECT_Z_MODE = First Wins
    DEAGGREGATE_INPUT = Yes
    GROUP_BY = ID Uber
    AREA -> AttributeManager_59

Bookmark: This should be a loop - but dissolver blocks it _Uber 14
AttributeManager_59
    ATTR_TABLE = SET_TO Uber (uint64) = @sum(@Value(Uber),2)
    -> NeighborFinder_27 [BASE]
NeighborFinder_27
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_27
ListElementCounter_27
    CNT_ATTR = _element_count
    LIST_NAME = Finds{}
    -> Tester_30
Tester_30
    BOOL_OP = OR
    TEST_CLAUSE = TEST @Value(_element_count) = @Evaluate(@pow(@Value(Uber),2))
    TEST_MODE = TEST
    PASSED -> ListExploder_26
    FAILED -> AttributeManager_60
AttributeManager_60
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_17
ListExploder_26
    ATTR_ACCUM_MODE = Merge List Attributes
    ATTR_CONFLICT_RES = Use List Attribute Values
    INDEX_ATTR = _element_index
    LIST_ATTR = Finds{}
    ELEMENTS -> FeatureJoiner_27 [RIGHT]
FeatureJoiner_27
    ATTR_CONFLICT_RES = Prefer Left
    GEOMETRY_HANDLING = Prefer Left
    JOIN_KEYS = ID_Ref ID_Ref AUTO
    JOIN_MODE = Inner
    JOINED -> Dissolver_25
Dissolver_25
    ACCUM_INPUT_ATTRS = Drop Incoming Attributes
    CLEANING_TOLERANCE = Automatic
    CONNECT_Z_MODE = First Wins
    DEAGGREGATE_INPUT = Yes
    GROUP_BY = ID Uber
    AREA -> AttributeManager_61

Bookmark: This should be a loop - but dissolver blocks it _Uber 16
AttributeManager_61
    ATTR_TABLE = SET_TO Uber (uint64) = @sum(@Value(Uber),2)
    -> NeighborFinder_28 [BASE]
NeighborFinder_28
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_28
ListElementCounter_28
    CNT_ATTR = _element_count
    LIST_NAME = Finds{}
    -> Tester_31
Tester_31
    BOOL_OP = OR
    TEST_CLAUSE = TEST @Value(_element_count) = @Evaluate(@pow(@Value(Uber),2))
    TEST_MODE = TEST
    PASSED -> ListExploder_27
    FAILED -> AttributeManager_62
AttributeManager_62
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_17
ListExploder_27
    ATTR_ACCUM_MODE = Merge List Attributes
    ATTR_CONFLICT_RES = Use List Attribute Values
    INDEX_ATTR = _element_index
    LIST_ATTR = Finds{}
    ELEMENTS -> FeatureJoiner_28 [RIGHT]
FeatureJoiner_28
    ATTR_CONFLICT_RES = Prefer Left
    GEOMETRY_HANDLING = Prefer Left
    JOIN_KEYS = ID_Ref ID_Ref AUTO
    JOIN_MODE = Inner
    JOINED -> Dissolver_26
Dissolver_26
    ACCUM_INPUT_ATTRS = Drop Incoming Attributes
    CLEANING_TOLERANCE = Automatic
    CONNECT_Z_MODE = First Wins
    DEAGGREGATE_INPUT = Yes
    GROUP_BY = ID Uber
    AREA -> AttributeManager_63

Bookmark: This should be a loop - but dissolver blocks it _Uber 18
AttributeManager_63
    ATTR_TABLE = SET_TO Uber (uint64) = @sum(@Value(Uber),2)
    -> NeighborFinder_29 [BASE]
NeighborFinder_29
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_29
ListElementCounter_29
    CNT_ATTR = _element_count
    LIST_NAME = Finds{}
    -> Tester_32
Tester_32
    BOOL_OP = OR
    TEST_CLAUSE = TEST @Value(_element_count) = @Evaluate(@pow(@Value(Uber),2))
    TEST_MODE = TEST
    PASSED -> ListExploder_28
    FAILED -> AttributeManager_64
AttributeManager_64
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_17
ListExploder_28
    ATTR_ACCUM_MODE = Merge List Attributes
    ATTR_CONFLICT_RES = Use List Attribute Values
    INDEX_ATTR = _element_index
    LIST_ATTR = Finds{}
    ELEMENTS -> FeatureJoiner_29 [RIGHT]
FeatureJoiner_29
    ATTR_CONFLICT_RES = Prefer Left
    GEOMETRY_HANDLING = Prefer Left
    JOIN_KEYS = ID_Ref ID_Ref AUTO
    JOIN_MODE = Inner
    JOINED -> Dissolver_27
Dissolver_27
    ACCUM_INPUT_ATTRS = Drop Incoming Attributes
    CLEANING_TOLERANCE = Automatic
    CONNECT_Z_MODE = First Wins
    DEAGGREGATE_INPUT = Yes
    GROUP_BY = ID Uber
    AREA -> AttributeManager_48

Bookmark: This should be a loop - but dissolver blocks it _Uber 20
AttributeManager_48
    ATTR_TABLE = SET_TO Uber (uint64) = @sum(@Value(Uber),2)
    -> NeighborFinder_30 [BASE]
NeighborFinder_30
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_30
ListElementCounter_30
    CNT_ATTR = _element_count
    LIST_NAME = Finds{}
    -> Tester_33
Tester_33
    BOOL_OP = OR
    TEST_CLAUSE = TEST @Value(_element_count) = @Evaluate(@pow(@Value(Uber),2))
    TEST_MODE = TEST
    PASSED -> ListExploder_29
    FAILED -> AttributeManager_65
AttributeManager_65
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_19
ListExploder_29
    ATTR_ACCUM_MODE = Merge List Attributes
    ATTR_CONFLICT_RES = Use List Attribute Values
    INDEX_ATTR = _element_index
    LIST_ATTR = Finds{}
    ELEMENTS -> FeatureJoiner_30 [RIGHT]
FeatureJoiner_30
    ATTR_CONFLICT_RES = Prefer Left
    GEOMETRY_HANDLING = Prefer Left
    JOIN_KEYS = ID_Ref ID_Ref AUTO
    JOIN_MODE = Inner
    JOINED -> Dissolver_28
Dissolver_28
    ACCUM_INPUT_ATTRS = Drop Incoming Attributes
    CLEANING_TOLERANCE = Automatic
    CONNECT_Z_MODE = First Wins
    DEAGGREGATE_INPUT = Yes
    GROUP_BY = ID Uber
    AREA -> AttributeManager_66

Bookmark: This should be a loop - but dissolver blocks it _Uber 22
AttributeManager_66
    ATTR_TABLE = SET_TO Uber (uint64) = @sum(@Value(Uber),2)
    -> NeighborFinder_31 [BASE]
NeighborFinder_31
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_31
ListElementCounter_31
    CNT_ATTR = _element_count
    LIST_NAME = Finds{}
    -> Tester_34
Tester_34
    BOOL_OP = OR
    TEST_CLAUSE = TEST @Value(_element_count) = @Evaluate(@pow(@Value(Uber),2))
    TEST_MODE = TEST
    PASSED -> ListExploder_30
    FAILED -> AttributeManager_67
AttributeManager_67
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_19
ListExploder_30
    ATTR_ACCUM_MODE = Merge List Attributes
    ATTR_CONFLICT_RES = Use List Attribute Values
    INDEX_ATTR = _element_index
    LIST_ATTR = Finds{}
    ELEMENTS -> FeatureJoiner_31 [RIGHT]
FeatureJoiner_31
    ATTR_CONFLICT_RES = Prefer Left
    GEOMETRY_HANDLING = Prefer Left
    JOIN_KEYS = ID_Ref ID_Ref AUTO
    JOIN_MODE = Inner
    JOINED -> Dissolver_29
Dissolver_29
    ACCUM_INPUT_ATTRS = Drop Incoming Attributes
    CLEANING_TOLERANCE = Automatic
    CONNECT_Z_MODE = First Wins
    DEAGGREGATE_INPUT = Yes
    GROUP_BY = ID Uber
    AREA -> AttributeManager_68

Bookmark: This should be a loop - but dissolver blocks it _Uber 24
AttributeManager_68
    ATTR_TABLE = SET_TO Uber (uint64) = @sum(@Value(Uber),2)
    -> NeighborFinder_32 [BASE]
NeighborFinder_32
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_32
ListElementCounter_32
    CNT_ATTR = _element_count
    LIST_NAME = Finds{}
    -> Tester_35
Tester_35
    BOOL_OP = OR
    TEST_CLAUSE = TEST @Value(_element_count) = @Evaluate(@pow(@Value(Uber),2))
    TEST_MODE = TEST
    PASSED -> ListExploder_31
    FAILED -> AttributeManager_69
AttributeManager_69
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_19
ListExploder_31
    ATTR_ACCUM_MODE = Merge List Attributes
    ATTR_CONFLICT_RES = Use List Attribute Values
    INDEX_ATTR = _element_index
    LIST_ATTR = Finds{}
    ELEMENTS -> FeatureJoiner_32 [RIGHT]
FeatureJoiner_32
    ATTR_CONFLICT_RES = Prefer Left
    GEOMETRY_HANDLING = Prefer Left
    JOIN_KEYS = ID_Ref ID_Ref AUTO
    JOIN_MODE = Inner
    JOINED -> Dissolver_30
Dissolver_30
    ACCUM_INPUT_ATTRS = Drop Incoming Attributes
    CLEANING_TOLERANCE = Automatic
    CONNECT_Z_MODE = First Wins
    DEAGGREGATE_INPUT = Yes
    GROUP_BY = ID Uber
    AREA -> AttributeManager_70

Bookmark: This should be a loop - but dissolver blocks it _Uber 26
AttributeManager_70
    ATTR_TABLE = SET_TO Uber (uint64) = @sum(@Value(Uber),2)
    -> NeighborFinder_33 [BASE]
NeighborFinder_33
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_33
ListElementCounter_33
    CNT_ATTR = _element_count
    LIST_NAME = Finds{}
    -> Tester_36
Tester_36
    BOOL_OP = OR
    TEST_CLAUSE = TEST @Value(_element_count) = @Evaluate(@pow(@Value(Uber),2))
    TEST_MODE = TEST
    PASSED -> ListExploder_32
    FAILED -> AttributeManager_71
AttributeManager_71
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_19
ListExploder_32
    ATTR_ACCUM_MODE = Merge List Attributes
    ATTR_CONFLICT_RES = Use List Attribute Values
    INDEX_ATTR = _element_index
    LIST_ATTR = Finds{}
    ELEMENTS -> FeatureJoiner_33 [RIGHT]
FeatureJoiner_33
    ATTR_CONFLICT_RES = Prefer Left
    GEOMETRY_HANDLING = Prefer Left
    JOIN_KEYS = ID_Ref ID_Ref AUTO
    JOIN_MODE = Inner
    JOINED -> Dissolver_31
Dissolver_31
    ACCUM_INPUT_ATTRS = Drop Incoming Attributes
    CLEANING_TOLERANCE = Automatic
    CONNECT_Z_MODE = First Wins
    DEAGGREGATE_INPUT = Yes
    GROUP_BY = ID Uber
    AREA -> AttributeManager_72

Bookmark: This should be a loop - but dissolver blocks it _Uber 28
AttributeManager_72
    ATTR_TABLE = SET_TO Uber (uint64) = @sum(@Value(Uber),2)
    -> NeighborFinder_34 [BASE]
NeighborFinder_34
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_34
ListElementCounter_34
    CNT_ATTR = _element_count
    LIST_NAME = Finds{}
    -> Tester_37
Tester_37
    BOOL_OP = OR
    TEST_CLAUSE = TEST @Value(_element_count) = @Evaluate(@pow(@Value(Uber),2))
    TEST_MODE = TEST
    PASSED -> ListExploder_33
    FAILED -> AttributeManager_73
AttributeManager_73
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_21
ListExploder_33
    ATTR_ACCUM_MODE = Merge List Attributes
    ATTR_CONFLICT_RES = Use List Attribute Values
    INDEX_ATTR = _element_index
    LIST_ATTR = Finds{}
    ELEMENTS -> FeatureJoiner_34 [RIGHT]
FeatureJoiner_34
    ATTR_CONFLICT_RES = Prefer Left
    GEOMETRY_HANDLING = Prefer Left
    JOIN_KEYS = ID_Ref ID_Ref AUTO
    JOIN_MODE = Inner
    JOINED -> Dissolver_32
Dissolver_32
    ACCUM_INPUT_ATTRS = Drop Incoming Attributes
    CLEANING_TOLERANCE = Automatic
    CONNECT_Z_MODE = First Wins
    DEAGGREGATE_INPUT = Yes
    GROUP_BY = ID Uber
    AREA -> AttributeManager_74

Bookmark: This should be a loop - but dissolver blocks it _Uber 30
AttributeManager_74
    ATTR_TABLE = SET_TO Uber (uint64) = @sum(@Value(Uber),2)
    -> NeighborFinder_35 [BASE]
NeighborFinder_35
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_35
ListElementCounter_35
    CNT_ATTR = _element_count
    LIST_NAME = Finds{}
    -> Tester_38
Tester_38
    BOOL_OP = OR
    TEST_CLAUSE = TEST @Value(_element_count) = @Evaluate(@pow(@Value(Uber),2))
    TEST_MODE = TEST
    PASSED -> ListExploder_34
    FAILED -> AttributeManager_75
AttributeManager_75
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_21
ListExploder_34
    ATTR_ACCUM_MODE = Merge List Attributes
    ATTR_CONFLICT_RES = Use List Attribute Values
    INDEX_ATTR = _element_index
    LIST_ATTR = Finds{}
    ELEMENTS -> FeatureJoiner_35 [RIGHT]
FeatureJoiner_35
    ATTR_CONFLICT_RES = Prefer Left
    GEOMETRY_HANDLING = Prefer Left
    JOIN_KEYS = ID_Ref ID_Ref AUTO
    JOIN_MODE = Inner
    JOINED -> Dissolver_33
Dissolver_33
    ACCUM_INPUT_ATTRS = Drop Incoming Attributes
    CLEANING_TOLERANCE = Automatic
    CONNECT_Z_MODE = First Wins
    DEAGGREGATE_INPUT = Yes
    GROUP_BY = ID Uber
    AREA -> AttributeManager_76

Bookmark: This should be a loop - but dissolver blocks it _Uber 32
AttributeManager_76
    ATTR_TABLE = SET_TO Uber (uint64) = @sum(@Value(Uber),2)
    -> NeighborFinder_36 [BASE]
NeighborFinder_36
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_36
ListElementCounter_36
    CNT_ATTR = _element_count
    LIST_NAME = Finds{}
    -> Tester_39
Tester_39
    BOOL_OP = OR
    TEST_CLAUSE = TEST @Value(_element_count) = @Evaluate(@pow(@Value(Uber),2))
    TEST_MODE = TEST
    PASSED -> ListExploder_35
    FAILED -> AttributeManager_77
AttributeManager_77
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_21
ListExploder_35
    ATTR_ACCUM_MODE = Merge List Attributes
    ATTR_CONFLICT_RES = Use List Attribute Values
    INDEX_ATTR = _element_index
    LIST_ATTR = Finds{}
    ELEMENTS -> FeatureJoiner_36 [RIGHT]
FeatureJoiner_36
    ATTR_CONFLICT_RES = Prefer Left
    GEOMETRY_HANDLING = Prefer Left
    JOIN_KEYS = ID_Ref ID_Ref AUTO
    JOIN_MODE = Inner
    JOINED -> Dissolver_34
Dissolver_34
    ACCUM_INPUT_ATTRS = Drop Incoming Attributes
    CLEANING_TOLERANCE = Automatic
    CONNECT_Z_MODE = First Wins
    DEAGGREGATE_INPUT = Yes
    GROUP_BY = ID Uber
    AREA -> AttributeManager_78

Bookmark: This should be a loop - but dissolver blocks it _Uber 34
AttributeManager_78
    ATTR_TABLE = SET_TO Uber (uint64) = @sum(@Value(Uber),2)
    -> NeighborFinder_37 [BASE]
NeighborFinder_37
    CANDIDATES_FIRST = No
    CLOSE_LIST_ATTRS_TO_INCLUDE = ID_Ref
    CLOSE_LIST_ATTRS_TO_INCLUDE_MODE = Selected Attributes
    CLOSE_LIST_NAME = Finds
    INSERT_VERTEX = No
    K = @pow(@Value(Uber),2)
    MAX = 1
    MEASURES_FROM_CANDIDATE = Yes
    MEASURE_TYPE = Continuous
    MODE = Bases and Candidates
    TREAT_POLYGON_AS = Areas
    MATCHED -> ListElementCounter_37
ListElementCounter_37
    CNT_ATTR = _element_count
    LIST_NAME = Finds{}
    -> Tester_40
Tester_40
    BOOL_OP = OR
    TEST_CLAUSE = TEST @Value(_element_count) = @Evaluate(@pow(@Value(Uber),2))
    TEST_MODE = TEST
    PASSED -> ListExploder_36
    FAILED -> AttributeManager_79
AttributeManager_79
    ATTR_TABLE:
      SET_TO Uber (uint64) = @sub(@Value(Uber),2)
      REMOVE Finds{}.ID_Ref (int64)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE Finds{}.distance (real64)
      REMOVE Finds{}.angle (real64)
      REMOVE Finds{}.candidate_angle (real64)
      REMOVE Finds{}.candidate_label_angle (real64)
      REMOVE Finds{}.closest_candidate_x (real64)
      REMOVE Finds{}.closest_candidate_y (real64)
      REMOVE Finds{}.closest_base_x (real64)
      REMOVE Finds{}.closest_base_y (real64)
      REMOVE _element_count (uint64)
    -> Junction_21
ListExploder_36
    ATTR_ACCUM_MODE = Merge List Attributes
    ATTR_CONFLICT_RES = Use List Attribute Values
    INDEX_ATTR = _element_index
    LIST_ATTR = Finds{}
    ELEMENTS -> FeatureJoiner_37 [RIGHT]
FeatureJoiner_37
    ATTR_CONFLICT_RES = Prefer Left
    GEOMETRY_HANDLING = Prefer Left
    JOIN_KEYS = ID_Ref ID_Ref AUTO
    JOIN_MODE = Inner
    JOINED -> Dissolver_35
Dissolver_35
    ACCUM_INPUT_ATTRS = Drop Incoming Attributes
    CLEANING_TOLERANCE = Automatic
    CONNECT_Z_MODE = First Wins
    DEAGGREGATE_INPUT = Yes
    GROUP_BY = ID Uber
